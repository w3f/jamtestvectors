-- Tiny Constants

Constants DEFINITIONS ::= BEGIN

-- True constants

validators-count INTEGER ::= 6
core-count INTEGER ::= 2
epoch-length INTEGER ::= 12

max-tickets-per-block INTEGER ::= 3
tickets-per-validator INTEGER ::= 3

-- Derived constants

-- ceil(validators-count * 2/3 + 1)
validators-super-majority INTEGER ::= 5
-- floor((core-count + 7) / 8)
avail-bitfield-bytes INTEGER ::= 1

END
