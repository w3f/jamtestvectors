-- Syntax for Safrole protocol test vectors

SafroleModule DEFINITIONS ::= BEGIN

-- Define constants
validators_count INTEGER ::= 6
epoch_length INTEGER ::= 12

-- Define basic types
u8 ::= INTEGER (0..255)
u32 ::= INTEGER (0..4294967295)

-- Define fixed-length arrays
ByteArray32 ::= SEQUENCE (SIZE(32)) OF u8
OpaqueHash ::= ByteArray32
Ed25519Key ::= ByteArray32
BlsKey ::= SEQUENCE (SIZE(144)) OF u8
BandersnatchKey ::= ByteArray32
EpochKeys ::= SEQUENCE (SIZE(epoch_length)) OF BandersnatchKey
TicketsBodies ::= SEQUENCE (SIZE(epoch_length)) OF TicketBody

-- Define enumerations
TicketsOrKeys ::= ENUMERATED {
    tickets (0),
    keys (1)
}

-- Define structures
TicketBody ::= SEQUENCE {
    id OpaqueHash,
    attempt u8
}

ValidatorData ::= SEQUENCE {
    ed25519 Ed25519Key,
    bandersnatch BandersnatchKey,
    bls BlsKey,
    metadata SEQUENCE (SIZE(128)) OF u8
}

ValidatorsData ::= SEQUENCE (SIZE(validators_count)) OF ValidatorData

TicketEnvelope ::= SEQUENCE {
    attempt u8,
    signature SEQUENCE (SIZE(784)) OF u8
}

EpochMark ::= SEQUENCE {
    entropy OpaqueHash,
    validators SEQUENCE (SIZE(validators_count)) OF BandersnatchKey
}

TicketsMark ::= SEQUENCE (SIZE(epoch_length)) OF TicketBody

-- Output markers.
OutputMarks ::= SEQUENCE {
    -- New epoch signal.
    epoch_mark [0] EpochMark OPTIONAL,
    -- Tickets signal.
    tickets_mark [1] TicketsMark OPTIONAL
}

-- State relevant to Safrole protocol
State ::= SEQUENCE {
    -- tau: The most recent block's timeslog.
    timeslot u32,
    -- eta: The entropy accumulator and epochal randomness.
    entropy SEQUENCE (SIZE(4)) OF OpaqueHash,
    -- lambda: The validator keys and metadata which were active in the prior epoch.
    prev_validators ValidatorsData,
    -- kappa: The validator keys and metadata currently active.
    curr_validators ValidatorsData,
    -- gamma_k: The validator keys for the following epoch.
    next_validators ValidatorsData,
    -- iota: The validator keys and metadata to be drawn from next.
    designed_validators ValidatorsData,
    -- gamma_a: The sealing-key contest ticket accumulator.
    tickets_accumulator SEQUENCE (SIZE(0..epoch_length)) OF TicketBody,
    -- gamma_s: The sealing-key series of the current epoch.
    tickets_or_keys TicketsOrKeys,
    -- gamma_z: The Bandersnatch ring root.
    tickets_verifier_key SEQUENCE (SIZE(384)) OF u8
}

-- Input for Safrole protocol.
Input ::= SEQUENCE {
    -- Current slot.
    slot u32,
    -- Per block entropy (originated from block entropy source VRF).
    entropy OpaqueHash,
    -- Safrole extrinsics (aka tickets evelopes).
    extrinsics SEQUENCE (SIZE(0..16)) OF TicketEnvelope
}

-- Output from Safrole protocol
Output ::= CHOICE {
    -- Markers
    ok OutputMarks,
    -- Error code (not in the spec, feel free to ignore the actual)
    err u8
}

-- Safrole state transition function execution dump
ExecDump ::= SEQUENCE {
    -- Input.
    input Input,
    -- Pre-execution state.
    pre_state State,
    -- Output.
    output Output,
    -- Post-execution state.
    post_state State
}

END
