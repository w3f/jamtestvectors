-- Syntax for Safrole protocol test vectors

SafroleModule DEFINITIONS ::= BEGIN

-- Define constants
IMPORTS validators-count, epoch-length FROM SafroleConstants;

-- Define basic types
U8 ::= INTEGER (0..255)
U32 ::= INTEGER (0..4294967295)

-- Define fixed-length arrays
ByteArray32 ::= SEQUENCE (SIZE(32)) OF U8
OpaqueHash ::= ByteArray32
Ed25519Key ::= ByteArray32
BlsKey ::= SEQUENCE (SIZE(144)) OF U8
BandersnatchKey ::= ByteArray32
EpochKeys ::= SEQUENCE (SIZE(epoch-length)) OF BandersnatchKey
TicketsBodies ::= SEQUENCE (SIZE(epoch-length)) OF TicketBody

-- Define enumerations
TicketsOrKeys ::= CHOICE {
    tickets TicketsBodies,
    keys EpochKeys 
}

-- Define structures
TicketBody ::= SEQUENCE {
    id OpaqueHash,
    attempt U8
}

ValidatorData ::= SEQUENCE {
    ed25519 Ed25519Key,
    bandersnatch BandersnatchKey,
    bls BlsKey,
    metadata SEQUENCE (SIZE(128)) OF U8
}

ValidatorsData ::= SEQUENCE (SIZE(validators-count)) OF ValidatorData

TicketEnvelope ::= SEQUENCE {
    attempt U8,
    signature SEQUENCE (SIZE(784)) OF U8
}

EpochMark ::= SEQUENCE {
    entropy OpaqueHash,
    validators SEQUENCE (SIZE(validators-count)) OF BandersnatchKey
}

TicketsMark ::= SEQUENCE (SIZE(epoch-length)) OF TicketBody

-- Output markers.
OutputMarks ::= SEQUENCE {
    -- New epoch signal.
    epoch-mark [0] EpochMark OPTIONAL,
    -- Tickets signal.
    tickets-mark [1] TicketsMark OPTIONAL
}

-- State relevant to Safrole protocol
State ::= SEQUENCE {
    -- tau: The most recent block's timeslog.
    timeslot U32,

    -- eta: The entropy accumulator and epochal randomness.
    entropy SEQUENCE (SIZE(4)) OF OpaqueHash,

    -- lambda: The validator keys and metadata which were active in the prior epoch.
    prev-validators ValidatorsData,

    -- kappa: The validator keys and metadata currently active.
    curr-validators ValidatorsData,

    -- gamma_k: The validator keys for the following epoch.
    next-validators ValidatorsData,

    -- iota: The validator keys and metadata to be drawn from next.
    designed-validators ValidatorsData,

    -- gamma_a: The sealing-key contest ticket accumulator.
    tickets-accumulator SEQUENCE (SIZE(0..epoch-length)) OF TicketBody,

    -- gamma_s: The sealing-key series of the current epoch.
    tickets-or-keys TicketsOrKeys,

    -- gamma_z: The Bandersnatch ring root.
    tickets-verifier-key SEQUENCE (SIZE(384)) OF U8
}

-- Input for Safrole protocol.
Input ::= SEQUENCE {
    -- Current slot.
    slot U32,
    -- Per block entropy (originated from block entropy source VRF).
    entropy OpaqueHash,
    -- Safrole extrinsics (aka tickets evelopes).
    extrinsics SEQUENCE (SIZE(0..16)) OF TicketEnvelope
}

-- Output from Safrole protocol
Output ::= CHOICE {
    -- Markers
    ok OutputMarks,
    -- Error code (not in the spec, feel free to ignore the actual)
    err U8
}

-- Safrole state transition function execution dump
Testcase ::= SEQUENCE {
    -- Input.
    input Input,
    -- Pre-execution state.
    pre-state State,
    -- Output.
    output Output,
    -- Post-execution state.
    post-state State
}

END
