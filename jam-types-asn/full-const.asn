-- Full Constants

Constants DEFINITIONS ::= BEGIN

-- True constants

validators-count INTEGER ::= 1023
cores-count INTEGER ::= 341
epoch-length INTEGER ::= 600

max-tickets-per-block INTEGER ::= 16
tickets-per-validator INTEGER ::= 2

max-blocks-history INTEGER ::= 8

auth-pool-max-size INTEGER ::= 8
auth-queue-size INTEGER ::= 80

-- Derived constants

-- ceil(validators-count * 2/3 + 1)
validators-super-majority INTEGER ::= 683
-- floor((cores-count + 7) / 8)
avail-bitfield-bytes INTEGER ::= 43

END
