-- Preimages STF test vectors schema

PreimagesModule DEFINITIONS ::= BEGIN

IMPORTS
    TimeSlot, OpaqueHash, PreimagesExtrinsic, ServiceId, ByteSequence, ServicesStatistics, U32
        FROM JamTypes;


PreimagesMapEntry ::= SEQUENCE {
    hash OpaqueHash,
    blob ByteSequence
}

LookupMetaMapKey ::= SEQUENCE {
    hash OpaqueHash,
    length U32
}

LookupMetaMapEntry ::= SEQUENCE {
    key LookupMetaMapKey,
    value SEQUENCE OF TimeSlot
}

-- Service account information relevant for this STF.
Account ::= SEQUENCE {
    -- [a_p] Preimages blobs.
    preimages SEQUENCE OF PreimagesMapEntry,
    -- [a_l] Preimages lookup metadata.
    lookup-meta SEQUENCE OF LookupMetaMapEntry
}

AccountsMapEntry ::= SEQUENCE {
    id ServiceId,
    data Account
}

State ::= SEQUENCE {
	-- [δ] Relevant services account data. Refer to T(σ) in GP Appendix D.
    accounts SEQUENCE OF AccountsMapEntry,
	-- [π_S] Services statistics.
	-- Note: Only stats related to preimages STF are updated, in particular:
	-- provided_count (p.0), provided_size (p.1).
    statistics ServicesStatistics
}

Input ::= SEQUENCE {
    -- [E_P] Preimages extrinsic.
    preimages PreimagesExtrinsic,
    -- [H_t] Block's timeslot.
    slot TimeSlot
}

-- State transition function execution error.
-- Error codes **are not specified** in the the Graypaper.
-- Feel free to ignore the actual value.
ErrorCode ::= ENUMERATED {
    preimage-unneeded (0),
    preimages-not-sorted-unique (1)
}

Output ::= CHOICE {
    ok  NULL,
    err ErrorCode
}

TestCase ::= SEQUENCE {
    input        Input,
    pre-state    State,
    output       Output,
    post-state   State
}

END
