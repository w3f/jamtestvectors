-- Statistics STF test vectors schema

StatisticsModule DEFINITIONS ::= BEGIN

IMPORTS
    TimeSlot, ValidatorIndex, Statistics, Extrinsic, ValidatorsData
        FROM JamTypes;


State ::= SEQUENCE {
    -- [π] Prior statistics. Mutated to π'.
    statistics Statistics,
    -- [τ] Prior timeslot.
    slot TimeSlot,
    -- [κ'] Posterior active validators.
    curr-validators ValidatorsData
}

Input ::= SEQUENCE {
    -- [H_t] Block timeslot
    slot TimeSlot,
    -- [H_i] Block author
    author-index ValidatorIndex,
    -- [E] Extrinsic
    extrinsic Extrinsic
}

Output ::= NULL

-- Disputes STF execution dump
TestCase ::= SEQUENCE {
    input        Input,
    pre-state    State,
    output       Output,
    post-state   State
}

END
